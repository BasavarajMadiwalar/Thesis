module FlushGroupTable {
    yang-version 1;
    namespace "urn:opendaylight:params:xml:ns:yang:FlushGroupTable";
    prefix "flushGrp";

    revision "2018-12-01" {
        description "Initial revision of I4application model";
    }

    rpc flushGrpTable {
        description "flush Stored mDNS Packets";


    } // rpc flushGrpTable

}
