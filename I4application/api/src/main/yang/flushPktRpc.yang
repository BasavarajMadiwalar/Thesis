module flushPktRpc {
    yang-version 1;
    namespace "urn:opendaylight:params:xml:ns:yang:flushPktRpc";
    prefix "flushPkt";

    revision "2018-12-01" {
        description "Initial revision of I4application model";
    }

    rpc flushPkts {
        description "flush Stored mDNS Packets";


    } // rpc flushPkts

}
