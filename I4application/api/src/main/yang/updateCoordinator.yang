module updateCoordinator {
    yang-version 1;
    namespace "urn:opendaylight:params:xml:ns:yang:updateCoordinator";
    prefix "updateCoordinatorList";

    revision "2018-12-01" {
        description "Initial revision of I4application model";
    }

    rpc update-coordinator-list {
        description "Update Coordinator list using new data";


    } // rpc update-coordinator-list

}
