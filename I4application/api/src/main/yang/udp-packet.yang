module udp-packet {
  yang-version 1;
  namespace "urn:opendaylight:params:xml:ns:yang:udp";
  prefix udp;

  import ietf-inet-types {
    prefix inet;
    revision-date 2010-09-24;
  }

  import base-packet {
    prefix bpacket;
    revision-date 2014-05-28;
  }

  revision 2015-04-30 {
    description
      "UDP Packet Module.";
  }

  grouping udp-packet-fields {
    leaf source-port {
      type inet:port-number;
      description "UDP source port number";
    }

    leaf destination-port {
      type inet:port-number;
      description "UDP destination port number";
    }

    leaf length {
      type uint16;
      description "UDP packet length";
    }

    leaf checksum {
      type uint16;
      description "UDP header and data checksum";
    }

    uses bpacket:packet-fields;
  }

  notification udp-packet-received {
    uses bpacket:packet-chain-grp {
      augment "bpacket:packet-chain/bpacket:packet" {
        case udp-packet {
          uses udp-packet-fields;
        }
      }
    }
    uses bpacket:packet-payload;
  }
}
